BIC-DATA-COLLECTOR-MIB DEFINITIONS ::= BEGIN

IMPORTS
           enterprises,
           MODULE-IDENTITY,
           OBJECT-TYPE,
           OBJECT-IDENTITY,
           NOTIFICATION-TYPE
                      FROM SNMPv2-SMI
           TEXTUAL-CONVENTION,
           DisplayString
                      FROM SNMPv2-TC;

bicDataCollectorMIB MODULE-IDENTITY
        -- 1.3.6.1.4.1.9999.1.2
        LAST-UPDATED "200908181058Z"    -- Aug 08, 2009 10:58:00 AM
        ORGANIZATION "myriadgroup.com"
        CONTACT-INFO
                "http://www.myriadgroup.com"
        DESCRIPTION
                "The BIC-PROCESSES-MIB defines objects for the
                management of all the processes living in BIC platform"
        REVISION "200908181058Z"        -- Aug 08, 2009 10:58:00 AM
        DESCRIPTION
                "Initial version."
        ::= {bic 8}


-- Enterprise OIDs
------------------

--        internet          OBJECT IDENTIFIER ::= { iso(1) org(3) dod(6) 1 }
--        private           OBJECT IDENTIFIER ::= { internet 4 }
--        enterprises     OBJECT IDENTIFIER ::= { private 1 }
          myriadgroup    OBJECT IDENTIFIER ::= { enterprises 9999 }

-- Project OIDs
------------------
          bic                  OBJECT IDENTIFIER ::= { myriadgroup 1 }

----------------------------------------------------------------------------
-- Textual Conventions
----------------------
--
-- Note: Some of the TEXTUAL-CONVENTIONs defined in this module are
--       OCTET STRING with a 1023 size limitation (SIZE(0..1023)).
--
-- As per RFC2578, section 7.1.2.  OCTET STRING:
--
--       "The OCTET STRING type represents arbitrary binary or textual data.
--        Although the SMI-specified size limitation for this type is 65535
--        octets, MIB designers should realize that there may be
--        implementation and interoperability limitations for sizes in
--        excess of 255 octets."
--
-- As a consequence an agent implementing this MIB may decide to
-- restrict this maximum size to a lesser value than 1023, provided that
-- it makes it clear in an AGENT-CAPABILITY statement.
--
----------------------------------------------------------------------------
DataCollectorAlarmContent ::= TEXTUAL-CONVENTION
    STATUS       current
    DESCRIPTION
          "This the BIC alarm content object.

          This object syntax is equivalent to a DisplayString, but with a
          a 1023 bytes size limits (instead of 255 for a DisplayString).

          Note that the SNMP agent may have to truncate the string returned
          by the underlying API if it does not fit in this type.
          (1023 bytes max).
          "
    SYNTAX       OCTET STRING (SIZE (0..1023))


------------
-- Scalars and Tables
------------
dcSeverity  OBJECT-TYPE
  			SYNTAX  INTEGER (0..255)
  			MAX-ACCESS  read-only
  			STATUS  current
  			DESCRIPTION
          			"global environment alarm severity inside data collector."
  			::= {bicDataCollectorMIB 999}



dcAlarms        OBJECT IDENTIFIER
                        ::= { bicDataCollectorMIB 99 }

dcStatusAlarm     OBJECT-TYPE
                        SYNTAX  DataCollectorAlarmContent
                        MAX-ACCESS  read-only
                        STATUS  current
                        DESCRIPTION
                                "The working status of data collector in production platform."
                        ::= {dcAlarms 1}


------------
-- Traps
------------

dcTraps         OBJECT IDENTIFIER
                        ::= { bicDataCollectorMIB 1 }

dcStatusTrap NOTIFICATION-TYPE
                         OBJECTS {dcSeverity,dcStatusAlarm}
                         STATUS current
                         DESCRIPTION
                             "This notification(trap) is sent to indicate a status change of process."
                         ::= {dcTraps  1}


END
